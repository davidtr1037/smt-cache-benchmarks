Protocol {iso(1) identified-organization(3) dod(6) internet(1) security(5) mechanisms(5) pkix(7) id-mod(0) id-pkix1-implicit-88(2)}

DEFINITIONS IMPLICIT TAGS ::=

BEGIN

Choice ::= CHOICE { x INTEGER, y INTEGER }
Set ::= SET { x INTEGER, y INTEGER }

Message ::= SEQUENCE{
    i INTEGER,
    b BOOLEAN,
    os OCTET STRING,
    bs BIT STRING,
    id OBJECT IDENTIFIER,
    utcTime UTCTime,
    any ANY,
    choice Choice,
    set Set,
    n NULL
}

END
